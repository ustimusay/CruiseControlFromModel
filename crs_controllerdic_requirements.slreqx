# crs_controllerdic_requirements
crs_controllerdic.sldd データエントリの定義要件

## #1: Kp: PI制御の比例ゲイン (Functional)
PIコントローラの比例ゲイン（値: 20）。activated/getThrottleValue/PI controller サブシステムの Kp Gain ブロックで車速偏差に乗算され、比例スロットル成分を生成する。
- Rationale: 比例項は車速偏差に即応してスロットルを補正するために必要であり、Kp をデータディクショナリで管理することでパラメータチューニングをモデル変更なしに行える。

## #2: Ki: PI制御の積分ゲイン (Functional)
PIコントローラの積分ゲイン（値: 約0.2）。activated/getThrottleValue/PI controller サブシステムの離散積分器に適用され、車速偏差の積分値を積分スロットル成分に変換する。
- Rationale: 積分項は定常速度偏差をゼロに収束させるために必要であり、Ki をデータディクショナリで管理することでパラメータチューニングをモデル変更なしに行える。

## #3: Ts: 制御系サンプル時間 (Functional)
制御系のサンプル時間（値: 0.01 秒）。PI controller サブシステムの離散積分器（DTI）のサンプル時間として使用される。
- Rationale: 離散時間制御系のサンプル時間は積分演算の精度に直接影響するため、Ts を一元管理することで制御周期の変更をモデル全体に一貫して反映できる。

## #4: brake_threshold: ブレーキ圧の無効化閾値 (Functional)
ブレーキ圧の閾値（値: 5 %）。disableCaseDetection サブシステムで brakeP 入力がこの値を超えるとブレーキ操作と判断し、CC 強制無効化フラグを立てる。
- Rationale: ブレーキペダルのセンサーノイズや軽微な踏み込みによる誤検出を防ぐために閾値判定が必要であり、brake_threshold をデータディクショナリで管理することで車両特性に応じた調整を容易にする。

## #5: KeyON: キーON状態の定数値 (Functional)
キーON状態を表す列挙定数（値: 2）。disableCaseDetection サブシステムで key 入力がキーON状態と一致するかを判定するために使用される。
- Rationale: キーがON状態でない場合はクルーズコントロールを強制無効化する必要があるため、キーON状態の定数値を一元管理することで仕様変更時の修正箇所を最小化する。

## #6: ShiftDrive: ドライブギア状態の定数値 (Functional)
ドライブ（走行）ギアを表す列挙定数（値: 2）。disableCaseDetection サブシステムで gear 入力がドライブ状態と一致するかを判定するために使用される。
- Rationale: ドライブギア以外（パーキング・ニュートラル等）ではクルーズコントロールを強制無効化する必要があるため、ドライブギアの定数値を一元管理することで仕様変更時の修正箇所を最小化する。

## #7: tsp_min: 目標速度の下限値 (Functional)
クルーズコントロールの目標速度下限（値: 40 mph/km/h）。getNewTargetSpeed の飽和ブロック・outOfRange の下限判定・disabled サブシステムの初期目標速度として使用される。
- Rationale: 低速域ではクルーズコントロールの安定動作が保証できないため目標速度に下限が必要であり、tsp_min をデータディクショナリで管理することで動作範囲の仕様変更に一元対応できる。

## #8: tsp_max: 目標速度の上限値 (Functional)
クルーズコントロールの目標速度上限（値: 100 mph/km/h）。getNewTargetSpeed の飽和ブロックおよび outOfRange の上限判定で使用される。
- Rationale: 過度に高い目標速度への追従を防ぎ法規・安全上の上限速度を保証するために目標速度の上限制限が必要であり、tsp_max をデータディクショナリで管理することで法規変更や車種仕様変更に対応できる。

## #9: throt_min: スロットル指令値の下限値 (Functional)
スロットル指令値の下限（値: 0 %）。getThrottleValue サブシステムの飽和ブロック（Saturation2）でスロットル出力値の下限クランプに使用される。
- Rationale: スロットル指令値が負値にならないようにするため下限制限が必要であり、throt_min をデータディクショナリで管理することでアクチュエータ仕様の変更に対応できる。

## #10: throt_max: スロットル指令値の上限値 (Functional)
スロットル指令値の上限（値: 100 %）。getThrottleValue サブシステムの飽和ブロック（Saturation2）でスロットル出力値の上限クランプに使用される。
- Rationale: スロットル指令値がアクチュエータの物理的な動作範囲を超えないようにするため上限制限が必要であり、throt_max をデータディクショナリで管理することでアクチュエータ仕様の変更に対応できる。

## #11: target_inc_short: 短押しインクリメント時の目標速度増加量 (Functional)
インクリメントスイッチ短押し時の目標速度増加量（値: 1 mph/km/h）。getNewTargetSpeed サブシステムで短押しインクリメントモード時に目標速度へ加算される。
- Rationale: 短押し操作では一定量の速度ステップ増加が求められるため、target_inc_short をデータディクショナリで管理することで操作仕様の変更をモデル修正なしに反映できる。

## #12: target_inc_hold: 長押しインクリメント時の目標速度増加量 (Functional)
インクリメントスイッチ長押し時の目標速度増加量（値: 0.05 mph/km/h）。getNewTargetSpeed サブシステムで長押しインクリメントモード時に目標速度へ加算される。
- Rationale: 長押し操作では単ステップあたりの速度変化量を短押しより小さくすることで連続した細かい速度調整を可能にする必要がある。target_inc_hold をデータディクショナリで管理することで操作感のチューニングをモデル変更なしに行える。

## #13: target_dec_short: 短押しデクリメント時の目標速度減少量 (Functional)
デクリメントスイッチ短押し時の目標速度減少量（値: 1 mph/km/h）。getNewTargetSpeed サブシステムで短押しデクリメントモード時に目標速度から減算される。
- Rationale: 短押し操作では一定量の速度ステップ減少が求められるため、target_dec_short をデータディクショナリで管理することで操作仕様の変更をモデル修正なしに反映できる。

## #14: target_dec_hold: 長押しデクリメント時の目標速度減少量 (Functional)
デクリメントスイッチ長押し時の目標速度減少量（値: 0.05 mph/km/h）。getNewTargetSpeed サブシステムで長押しデクリメントモード時に目標速度から減算される。
- Rationale: 長押し操作では単ステップあたりの速度変化量を短押しより小さくすることで連続した細かい速度調整を可能にする必要がある。target_dec_hold をデータディクショナリで管理することで操作感のチューニングをモデル変更なしに行える。
