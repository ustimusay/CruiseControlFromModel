# crs_controller_requirements
crs_controller サブシステム機能要件

## #1: DriverSwRequest: ドライバースイッチ要求の正規化 (Container)
ドライバースイッチ入力（enbl, cncl, set, resume, inc, dec）を処理し、運転者の意図を表す統一要求信号 reqDrv に変換する。
- Rationale: 物理スイッチの押下パターンは多様かつ同時押しが発生しうるため、優先度付きのスイッチング論理で一意な要求へ正規化し、後段の状態機械が単一の入力で制 御判断できるようにする必要がある。

### #4: decrement: デクリメント要求の生成 (Container)
dec_sw が有効のとき、内部カウンタで計測した押下継続時間に基づき短押し用または長押し用のデクリメント要求を dec_out として出力する。スイッチが無効のときは else 入力をそのまま通過させる。
- Rationale: デクリメントスイッチによる速度減少操作では、単ステップ調整（短押し）と連続的な高速デクリメント（長押し）を区別する必要がある。これにより運転者は一つの物理スイッチで細かい調整と大きな調整の両方を行える。押下時間の検出がなければ、すべての押下が同一の単ステップ応答となってしまう。

#### #7: counter (in decrement): デクリメントスイッチ継続押下カウンタ (Functional)
入力（In1）が有効（非ゼロ）である連続サンプル数をカウントし、入力が無効になるとカウントをゼロにリセットする。
- Rationale: decrement サブシステムは適切な速度変化量を選択するために短押しと長押しを区別する必要がある。有効入力サンプルを積算するカウンタが、この判断に必要な離散時間ステップ単位の押下継続時間を提供する。

#### #41: デクリメント操作の列挙値定義 (Functional)
dec 操作の出力候補値（Dec_Short / Dec_Middle / Dec_Long）および 前サンプル比較用の参照値（Dec_Short / Dec_Middle / Dec_Long）を EnumeratedConstant ブロックとして定義する。
- Rationale: Dec_Short / Dec_Middle / Dec_Long の 3 段階の操作状態を列挙型定数として定義することで、Switch ブロックおよび RelationalOperator への入力が型安全になる。またインクリメント側（#45）と対称的な構造を持たせることで、モデルの可読性と対称性を維持する。

#### #42: デクリメント短押し検出 (Functional)
dec_sw が true のとき reqMode.Dec_Short を出力する。dec_sw が false のときは else 入力（inc/dec 以外のスイッチ要求）をパススルーする。
- Rationale: ドライバーがデクリメントスイッチを 1 サイクルだけ押した場合、目標速度を 1 ステップ下げる意図として扱う。dec_sw の true/false に応じてスイッチ出力を切り替えることで、短押し（1 サイクル）を最小操作単位として明確に定義する。

#### #43: デクリメント中押し昇格判定 (Functional)
前サンプル要求が reqMode.Dec_Short または reqMode.Dec_Middle である（RelationalOperator × 2 → OR）かつ dec_sw が継続して true（AND）の場合に reqMode.Dec_Middle を出力する。これによりスイッチの押し続けに伴う段階的昇格を実現する。
- Rationale: ドライバーがスイッチを押し続けた場合、単一ステップの繰り返し入力よりも「連続変化」の意図と解釈すべきである。前サンプルが Dec_Short または Dec_Middle かつ継続押下中という条件で Dec_Middle へ昇格させることにより、押し続けに応じた段階的な速度変化を実現する。

#### #44: デクリメント長押し状態の継続 (Functional)
前サンプル要求が reqMode.Dec_Long（RelationalOperator）かつ dec_sw が継続して true（AND）の場合に reqMode.Dec_Long を維持する。これにより長押し状態を次サンプルへ引き継ぎ、スロットル連続変化を実現する。
- Rationale: 一定時間以上押し続けた後（Dec_Long 到達後）は、スイッチを離すまで Dec_Long を維持し続けることで、ドライバーが指を離すまでスロットルが連続変化する「長押し連続加減速」を実現する。前サンプル継続チェックにより意図しない状態リセットを防ぐ。

### #5: increment: インクリメント要求の生成 (Container)
inc_sw が有効のとき、内部カウンタで計測した押下継続時間に基づき短押し用または長押し用のインクリメント要求を inc_out として出力する。スイッチが無効のときは else 入力をそのまま通過させる。
- Rationale: インクリメントスイッチによる速度増加操作では、単ステップ調整（短押し）と連続的な高速インクリメント（長押し）を区別する必要がある。これにより運転者は一つの物理スイッチで細かい調整と大きな調整の両方を行える。押下時間の検出がなければ、すべての押下が同一の単ステップ応答となってしまう。

#### #8: counter (in increment): インクリメントスイッチ継続押下カウンタ (Functional)
入力（In1）が有効（非ゼロ）である連続サンプル数をカウントし、入力が無効になるとカウントをゼロにリセットする。
- Rationale: increment サブシステムは適切な速度変化量を選択するために短押しと長押しを区別する必要がある。有効入力サンプルを積算するカウンタが、この判断に必要な離散時間ステップ単位の押下継続時間を提供する。

#### #45: インクリメント操作の列挙値定義 (Functional)
inc 操作の出力候補値（Inc_Short / Inc_Middle / Inc_Long）および 前サンプル比較用の参照値を EnumeratedConstant ブロックとして定義する。
- Rationale: Inc_Short / Inc_Middle / Inc_Long の 3 段階をデクリメント側（#41）と対称に定義することで、モデル構造の一貫性を保つ。インクリメント側でも型安全な列挙型定数を使用し、値の一元管理を実現する。

#### #46: インクリメント短押し検出 (Functional)
inc_sw が true のとき reqMode.Inc_Short を出力する。inc_sw が false のときは else 入力をパススルーする。
- Rationale: ドライバーがインクリメントスイッチを 1 サイクルだけ押した場合、目標速度を 1 ステップ上げる意図として扱う。デクリメント短押し（#42）と対称的な実装により、モデルの保守性と可読性を確保する。

#### #47: インクリメント中押し昇格判定 (Functional)
前サンプル要求が reqMode.Inc_Short または reqMode.Inc_Middle である（RelationalOperator × 2 → OR）かつ inc_sw が継続して true（AND）の場合に reqMode.Inc_Middle を出力する。
- Rationale: デクリメント中押し昇格（#43）と対称的な条件判定により、インクリメントスイッチの押し続けに応じた Inc_Middle への段階的昇格を実現する。ユーザー操作意図の連続性を一貫したロジックで表現する。

#### #48: インクリメント長押し状態の継続 (Functional)
前サンプル要求が reqMode.Inc_Long（RelationalOperator）かつ inc_sw が継続して true（AND）の場合に reqMode.Inc_Long を維持する。
- Rationale: デクリメント長押し継続（#44）と対称的な実装により、インクリメントスイッチの長押し中は Inc_Long を維持し、連続増速を実現する。対称構造とすることで inc/dec 間のレビューおよびテストを効率化できる。

### #6: doNot Repeat: 連続重複要求の除去 (Container)
入力要求（reqDrInv）が前回の要求と同じ場合、出力を「要求なし」の値に置き換える。異なる場合は入力をそのまま reqDrv として出力する。
- Rationale: 後段の状態機械は同じ要求を連続ステップで再処理してはならない。重複除去がなければ、スイッチを押し続けた場合に連続的なボタン押下と解釈され、意図しない状態遷移の繰り返しが発生する。

#### #49: 繰り返し禁止対象タイプの判定 (Functional)
現在の要求が Cancel / Cruise / Set / ResumeReq のいずれかであるかを RelationalOperator × 4 → OR で判定する。これらのモードは連続入力を抑制すべき "モメンタリ操作" に相当する。
- Rationale: Cancel / Cruise / Set / ResumeReq はいずれもスイッチの「押し始め」を契機とするモメンタリ操作であり、押し続けによる繰り返し実行は意図しない動作につながる。これらのタイプを OR 判定でグルーピングすることで、連続押下抑制の適用対象を明確に管理する。

#### #50: 前サンプル入力の保持（doNot Repeat） (Functional)
1 サンプル前の入力要求（reqDrInv）を Delay で保持し、次サンプルの同値比較（前サンプルとの同一性チェック）に使用する。
- Rationale: 同値判定（#51）では現在の入力と 1 サンプル前の入力を比較する必要があるが、前の入力値はサンプル周期をまたいで保持されない。Delay ブロックで前サンプル値を保持することで、次のサンプルで参照可能にする。

#### #51: 前サンプルとの同値判定 (Functional)
現在の要求（reqDrInv）と Delay の出力（前サンプル）が同値かを RelationalOperator で判定する。同値であれば「同一スイッチが連続して押されている」ことを示す。
- Rationale: モメンタリ操作の「連続押下」を検出するには、現在の要求が前サンプルと同一かどうかを判定する必要がある。RelationalOperator による同値比較により、「ボタンを押し続けて同一要求が継続している」状態を正確に識別する。

#### #52: 重複入力時の NoRequest 出力 (Functional)
繰り返し禁止対象タイプ（OR 出力）かつ前サンプルと同値（AND）の場合に reqMode.NoRequest を出力する。それ以外のときは reqDrInv をパススルーする（Switch）。
- Rationale: 繰り返し禁止対象（#49）かつ前サンプルと同値（#51）の場合に NoRequest を出力することで、ドライバーが意図した「1 回の押し操作」のみを有効とし、同一ボタンを押し続けることによる意図しない重複コマンドの発行を防止する。

### #38: 優先度選択定数の定義 (Functional)
cncl/enbl/set/resume の各スイッチ操作と無入力に対応する reqMode 列挙値（Cancel / Cruise / Set / ResumeReq / NoRequest）を EnumeratedConstant ブロックとして定義する。これらの値が優先度付き Switch チェーンの入力定数となる。
- Rationale: 各スイッチ入力に対応する reqMode 列挙値を定数ブロックとして一元定義することで、Switch チェーン全体で型安全な列挙型信号を使用できる。定数を個別に記述するのではなくブロックとして明示することで、値の変更が必要になった場合の修正箇所を一箇所に集約し、保守性を確保する。

### #39: 優先度付きスイッチ選択チェーン (Functional)
cncl > enbl > set > resume の優先度順に Switch ブロックを直列に接続し、有効な入力のうち最高優先度の reqMode を選択する。いずれの入力も false のときは dec/inc サブシステムの出力をパススルーする。
- Rationale: 複数スイッチが同時押しされた場合でも出力が一意に決まるよう、優先度順（cncl > enbl > set > resume）を明示的に実装する必要がある。キャンセルは走行安全上の停止要求であるため最高優先度とし、以降は操作変化量の大きい順に並べることで直感的な挙動を保証する。

### #40: 前サンプル要求の保持（DriverSwRequest） (Functional)
1 サンプル前の reqDrv を Delay で保持する。この値を doNot Repeat サブシステムおよび dec/inc サブシステムの prev_req（前サンプル要求）として供給する。
- Rationale: doNot Repeat サブシステムは現在要求と前サンプル要求の比較により連続重複を検出し、dec/inc サブシステムは前サンプル要求との比較により押し続け昇格を判定する。いずれも前サンプル値を必要とするため、DriverSwRequest 出力を 1 サンプル遅延させて供給する。

## #2: CruiseControlMode: クルーズコントロール動作モード管理 (Container)
reqDrv、brakeP、vehSp、key、gear を入力として、クルーズコントロールの動作状態（status）と制御モード（mode）を決定する。
- Rationale: 走行条件（車速範囲、ブレーキ操作、キーON/OFF、ギア位置）に応じた安全な状態遷移管理が必要であり、不正な状態への遷移を防ぐことで機能安全要件を満たす。

### #9: disableCaseDetection: CC強制無効化条件の判定 (Container)
key（キーON/OFF）、gear（ギア位置）、brakeP（ブレーキ圧）を入力として、クルーズコントロールを強制的に無効化すべき状態かどうかを示す disable_flag を出力する。
- Rationale: キーオフ・非走行ギア・ブレーキ操作はCCの継続を危険にするため、これらの条件を一元的に検出して後段のモード判定に伝える必要がある。

#### #53: IsKeyPositionOn: キーポジションON判定 (Container)
key 入力（KeyPosition 列挙型）と定数 KeyON を RelationalOperator で比較し、キーがON位置にないかどうかを判定する。
- Rationale: キーOFF状態ではクルーズコントロールを継続できないため、キー位置を監視し強制無効化の判断材料とする。

##### #59: IsKeyPositionOn: KeyON 参照定数 (Functional)
比較基準となる列挙定数 KeyON を供給する。
- Rationale: RelationalOperator の比較対象を定数ブロックとして定義することで、閾値の一元管理と可読性を確保する。

##### #60: IsKeyPositionOn: キー位置等値比較 (Functional)
key 入力と定数 KeyON を ~= 演算子で比較し、キーが ON 位置にない（true）かを出力する。
- Rationale: キーがON以外の場合に強制無効化フラグを立てるため、等値でない条件を検出する。

#### #54: IsShiftDrive: ドライブギア判定 (Container)
gear 入力（ShiftPosition 列挙型）と定数 ShiftDrive を RelationalOperator で比較し、ギアがドライブ位置にないかどうかを判定する。
- Rationale: ドライブレンジ以外（パーク、リバースなど）ではクルーズコントロールの動作が危険なため、ギア位置を監視して強制無効化の判断材料とする。

##### #61: IsShiftDrive: ShiftDrive 参照定数 (Functional)
比較基準となる列挙定数 ShiftDrive を供給する。
- Rationale: RelationalOperator の比較対象を定数ブロックとして定義することで、値の一元管理と可読性を確保する。

##### #62: IsShiftDrive: ギア位置等値比較 (Functional)
gear 入力と定数 ShiftDrive を ~= 演算子で比較し、ギアがドライブ位置にない（true）かを出力する。
- Rationale: ドライブ以外のギアポジションでは走行速度の維持制御が危険なため、非ドライブ状態を検出する。

#### #55: isbrake: ブレーキ踏込み判定 (Container)
ブレーキ圧（brakeP）が閾値（brake_threshold）を超えるかを Compare To Constant で判定する。
- Rationale: ドライバーがブレーキを踏んだ場合は即座にクルーズコントロールを解除する必要があるため、ブレーキ圧が閾値を超えているかを検出する。

##### #63: isbrake: ブレーキ圧閾値比較 (Functional)
brakeP が brake_threshold を超えるかを Compare To Constant（> brake_threshold）で判定し、踏込み状態（true）を出力する。
- Rationale: ブレーキ踏込みを検出してクルーズコントロールを即座に解除するため、物理センサ値を閾値と比較して踏込み有無を判定する。

#### #64: disableCaseDetection: 強制無効化条件 OR 統合 (Functional)
IsKeyPositionOn・IsShiftDrive・isbrake の3条件を OR で統合し、いずれか1つでも成立すれば disable_flag = true を出力する。
- Rationale: 安全上の強制無効化は複数の独立した条件のいずれかが成立した時点で即座に発動すべきであり、OR 論理でその要件を実装する。

### #10: getActStatus: CC有効化ステータスの生成 (Container)
現在の制御モード（mode）を入力として、クルーズコントロールが有効化されているかどうかを示す cc_act_status を出力する。
- Rationale: 上位システムがCCの有効化状態を知るためにはモード列挙値から二値ステータスへの変換が必要であり、他のサブシステムがモード値を直接参照せずに有効化状態を判断できるようにする必要がある。

#### #65: getActStatus: Disable モード参照定数 (Functional)
getActStatus 内で使用する比較基準定数 opMode.Disable を供給する。
- Rationale: 有効化判定の比較対象を定数ブロックで明示し、値の管理を一元化する。

#### #66: getActStatus: Enable モード参照定数 (Functional)
getActStatus 内で使用する比較基準定数 opMode.Enable を供給する。
- Rationale: 有効化判定の比較対象を定数ブロックで明示し、値の管理を一元化する。

#### #67: getActStatus: Disable との非等値比較 (Functional)
mode 入力と opMode.Disable を ~= 演算子で比較し、モードが Disable でない（true）かを判定する。
- Rationale: CC有効化ステータスの一方の条件として「Disable 以外であること」を独立して表現するため。

#### #68: getActStatus: Enable との等値比較 (Functional)
mode 入力と opMode.Enable を == 演算子で比較し、モードが Enable 状態かどうかを判定する。
- Rationale: Enable 状態の確認はCCが操作待ち（有効化前の待機）状態にあることを示すため、独立した比較ブロックとして定義する。

#### #69: getActStatus: 有効化ステータス AND 統合 (Functional)
Disable非等値判定と Enable等値判定の2条件を AND で統合し、cc_act_status を出力する。
- Rationale: CC が有効化状態（Disable でなく Enable でもある）にあることを両条件の積として定義し、信号一本でステータスを供給する。

### #11: outOfRange: 車速範囲外判定 (Container)
車速（vehSp）が制御可能範囲（tsp_min ～ tsp_max）外にある場合に真となる outRange フラグを出力する。
- Rationale: クルーズコントロールは一定の車速範囲内でのみ安全に動作できる。範囲外車速での有効化・アクティブ化を禁止するため、車速の範囲判定を専用サブシステムとして分離する必要がある。

#### #70: outOfRange: 下限速度比較 (Functional)
車速 vehSp が tsp_min 未満（< tsp_min）かどうかを Compare To Constant で判定する。
- Rationale: 目標速度の下限を下回る場合にCC動作を禁止するため、下限逸脱の検出を独立したブロックで実装する。

#### #71: outOfRange: 上限速度比較 (Functional)
車速 vehSp が tsp_max を超える（> tsp_max）かどうかを Compare To Constant で判定する。
- Rationale: 目標速度の上限を超える速度域ではCC動作が安全でないため、上限逸脱の検出を独立したブロックで実装する。

#### #72: outOfRange: 速度範囲外 OR 統合 (Functional)
下限未満と上限超過の2条件を OR で統合し、いずれか1つでも成立すれば outRange = true を出力する。
- Rationale: 下限・上限のどちらを外れても範囲外として扱うべきであり、OR でその仕様を実装する。

### #12: opMode: 動作モードの決定 (Container)
ドライバー要求（reqDrv）、車速範囲外フラグ（outRange）、前ステップのモード（mode_prev）を入力として、クルーズコントロールの動作モード（mode）を決定する。
- Rationale: CCの各動作モード（無効・有効・アクティブ・再開）への遷移は複数条件の組み合わせで決まるため、遷移ロジックを専用サブシステムに集約することで状態管理の整合性を保証する必要がある。

#### #13: activateCondition: アクティブモード遷移条件の統合判定 (Container)
reqDrv、mode_prev、outof_range を入力として、現在のステップでアクティブモードへ遷移すべきかどうかを示す yesno フラグを出力する。
- Rationale: アクティブモードへの遷移はアクティブ化要求・長押し待機・継続条件・再開条件の論理和で構成されるため、これらの部分条件を統合してアクティブ化の最終判定を一か所で行う必要がある。

##### #17: activate: アクティブ化要求の検出 (Container)
reqDrv がアクティブ化要求を示し、かつ車速が範囲内（outof_range = false）のとき、yesno = true を出力する。
- Rationale: アクティブ化は「アクティブ化スイッチ押下」かつ「車速が有効範囲内」の2条件の積であるため、これを独立したサブシステムで判定することで条件の追加・変更を局所化できる。

###### #101: activate: Set 要求参照定数 (Functional)
reqMode.Set 定数を供給し、reqDrv との比較に使用する。
- Rationale: アクティブ化のトリガーとなる Set 要求値を定数ブロックで管理する。

###### #102: activate: reqDrv と Set の等値比較 (Functional)
reqDrv と reqMode.Set を == で比較し、Setスイッチ押下を検出する。
- Rationale: アクティブ化要求（Setスイッチ）の検出を独立した比較ブロックで実装する。

###### #103: activate: outof_range NOT 変換 (Functional)
outof_range を NOT で反転し「速度が範囲内」を示す信号を生成する。
- Rationale: アクティブ化条件のうち「車速が範囲内」を論理 NOT で表現する。

###### #104: activate: アクティブ化 AND 統合 (Functional)
reqDrv==Set かつ 速度範囲内（NOT outof_range）の2条件を AND で統合し、yesno を出力する。
- Rationale: Setスイッチ押下と速度範囲内の両条件が揃ったときのみアクティブ化する仕様を AND で実装する。

##### #18: keepActivated: アクティブ状態の継続条件判定 (Container)
reqDrv と mode_prev から、アクティブ状態を継続すべき条件が成立するかを示す yesno を出力する。
- Rationale: set/resume/inc/dec等の要求が入力された場合にアクティブ状態を維持するロジックを分離することで、アクティブ継続条件の変更が他の遷移ロジックに影響しないようにする必要がある。

###### #105: keepActivated: Increment モード参照定数 (Functional)
opMode.Increment を供給し、mode_prev との比較に使用する。
- Rationale: アクティブ継続条件の判定基準値を定数ブロックで管理する。

###### #106: keepActivated: IncrementHold モード参照定数 (Functional)
opMode.IncrementHold を供給し、mode_prev との比較に使用する。
- Rationale: アクティブ継続条件の判定基準値を定数ブロックで管理する。

###### #107: keepActivated: Activate モード参照定数 (Functional)
opMode.Activate を供給し、mode_prev との比較に使用する。
- Rationale: アクティブ継続条件の判定基準値を定数ブロックで管理する。

###### #108: keepActivated: Decrement モード参照定数 (Functional)
opMode.Decrement を供給し、mode_prev との比較に使用する。
- Rationale: アクティブ継続条件の判定基準値を定数ブロックで管理する。

###### #109: keepActivated: DecrementHold モード参照定数 (Functional)
opMode.DecrementHold を供給し、mode_prev との比較に使用する。
- Rationale: アクティブ継続条件の判定基準値を定数ブロックで管理する。

###### #110: keepActivated: NoRequest 参照定数 (Functional)
reqMode.NoRequest を供給し、reqDrv との比較に使用する。
- Rationale: 操作要求なし判定の基準値を定数ブロックで管理する。

###### #111: keepActivated: mode_prev==Increment 等値比較 (Functional)
mode_prev と opMode.Increment を == で比較する。
- Rationale: アクティブ継続条件の各モード判定を独立ブロックで実装する。

###### #112: keepActivated: mode_prev==IncrementHold 等値比較 (Functional)
mode_prev と opMode.IncrementHold を == で比較する。
- Rationale: アクティブ継続条件の各モード判定を独立ブロックで実装する。

###### #113: keepActivated: mode_prev==Activate 等値比較 (Functional)
mode_prev と opMode.Activate を == で比較する。
- Rationale: アクティブ継続条件の各モード判定を独立ブロックで実装する。

###### #114: keepActivated: mode_prev==Decrement 等値比較 (Functional)
mode_prev と opMode.Decrement を == で比較する。
- Rationale: アクティブ継続条件の各モード判定を独立ブロックで実装する。

###### #115: keepActivated: mode_prev==DecrementHold 等値比較 (Functional)
mode_prev と opMode.DecrementHold を == で比較する。
- Rationale: アクティブ継続条件の各モード判定を独立ブロックで実装する。

###### #116: keepActivated: reqDrv!=NoRequest 非等値比較 (Functional)
reqDrv と reqMode.NoRequest を ~= で比較し、操作要求が存在することを確認する。
- Rationale: アクティブ継続のためには操作要求がある（NoRequest でない）ことが必要であり、その条件を独立して表現する。

###### #117: keepActivated: アクティブモード OR 統合 (Functional)
5種のアクティブ系モード（Increment/IncrementHold/Activate/Decrement/DecrementHold）の等値比較を OR で統合する。
- Rationale: 前サンプルがアクティブ系モードのいずれかであることを OR でまとめ、継続判定の前提条件とする。

###### #118: keepActivated: アクティブ継続 AND 統合 (Functional)
アクティブモード OR 結果と reqDrv!=NoRequest を AND で統合し、yesno を出力する。
- Rationale: アクティブ状態を維持するための両条件を AND でまとめ、継続判定を完成させる。

##### #19: resumeToActive: Resume状態からActiveへの遷移条件判定 (Container)
前ステップのモード（mode_prev）がResume状態であった場合に yesno = true を出力する。
- Rationale: Resume状態から次ステップでActive状態へ自動遷移するルールを独立したサブシステムに分離することで、Resumeモードの遷移仕様を明確に表現し保守性を高める必要がある。

###### #119: resumeToActive: Resume モード参照定数 (Functional)
opMode.Resume 定数を供給し、mode_prev との比較に使用する。
- Rationale: Resume からのアクティブ遷移条件の判定基準値を定数ブロックで管理する。

###### #120: resumeToActive: mode_prev==Resume 等値比較 (Functional)
mode_prev と opMode.Resume を == で比較し、前サンプルが Resume 状態かどうかを判定する。yesno として出力。
- Rationale: Resume 状態からのアクティブ化への自動遷移条件を単一の等値比較で実装する。

##### #20: waitingForButtonHolding: ボタン長押し待機状態の判定 (Container)
reqDrv が長押し待機に対応する要求値のいずれかと一致する場合に yesno = true を出力する。
- Rationale: 長押し操作中にアクティブモードへの遷移を継続させるためには長押し中の要求値を検出する専用ロジックが必要であり、これを分離することで長押し判定の定義を一か所に集約できる。

###### #121: waitingForButtonHolding: Dec_Middle 参照定数 (Functional)
reqMode.Dec_Middle 定数を供給し、reqDrv との比較に使用する。
- Rationale: 長押し待機状態の判定に使用するデクリメント中押し値を定数ブロックで管理する。

###### #122: waitingForButtonHolding: Inc_Middle 参照定数 (Functional)
reqMode.Inc_Middle 定数を供給し、reqDrv との比較に使用する。
- Rationale: 長押し待機状態の判定に使用するインクリメント中押し値を定数ブロックで管理する。

###### #123: waitingForButtonHolding: reqDrv==Dec_Middle 等値比較 (Functional)
reqDrv と reqMode.Dec_Middle を == で比較し、デクリメント中押し待機を検出する。
- Rationale: 長押し待機への遷移条件の一方（Dec_Middle）を独立して表現する。

###### #124: waitingForButtonHolding: reqDrv==Inc_Middle 等値比較 (Functional)
reqDrv と reqMode.Inc_Middle を == で比較し、インクリメント中押し待機を検出する。
- Rationale: 長押し待機への遷移条件の他方（Inc_Middle）を独立して表現する。

###### #125: waitingForButtonHolding: 中押し待機 OR 統合 (Functional)
Dec_Middle 一致と Inc_Middle 一致の2条件を OR で統合し、yesno を出力する。
- Rationale: inc/dec いずれかの中押し状態であれば長押し待機と判定する仕様を OR で実装する。

##### #100: activateCondition: アクティブ化条件 OR 統合 (Functional)
activate・keepActivated・resumeToActive・waitingForButtonHolding の4条件を OR で統合し、いずれかが true であればアクティブ化条件成立を出力する。
- Rationale: アクティブ化への複数の経路を OR でまとめることで、各条件を独立してテストしながら統合判定を一つのブロックに集約する。

#### #14: disableCondition: 無効化条件の統合判定 (Container)
CCスイッチ要求（ccsw_request）と前ステップのモード（mode_prev）から、クルーズコントロールを無効化すべきかを示す yesno フラグを出力する。
- Rationale: 無効化はCC停止操作とアクティブ時のみ有効なボタン操作の論理和で決まるため、各判定を子サブシステムに分離しつつ最終判定をここで統合する必要がある。

##### #21: turnOffCruise: CC停止要求の検出 (Container)
ccsw_request がキャンセル要求であり、かつ mode_prev が非Disabled状態のとき、yesno = true を出力する。
- Rationale: 運転者がCCキャンセルを操作したとき、かつシステムが既に無効でない場合に限り無効化を発動することで、二重無効化や不要なモード遷移を防ぐ必要がある。

###### #135: turnOffCruise: Cruise 参照定数 (Functional)
reqMode.Cruise 定数を供給し、ccsw_request との比較に使用する。
- Rationale: CC停止のトリガー判定（キャンセル）基準値を定数ブロックで管理する。

###### #136: turnOffCruise: Disable モード参照定数 (Functional)
opMode.Disable 定数を供給し、mode_prev との比較に使用する。
- Rationale: CC停止条件のモード判定基準値を定数ブロックで管理する。

###### #137: turnOffCruise: ccsw_request!=Cruise 非等値比較 (Functional)
ccsw_request と reqMode.Cruise を ~= で比較し、キャンセル操作かを判定する。
- Rationale: Cruise以外の要求（キャンセル系）を検出してCC停止を判断する。

###### #138: turnOffCruise: mode_prev!=Disable 等値比較 (Functional)
mode_prev と opMode.Disable を == で比較し、既に Disable でないかを確認する。
- Rationale: すでに Disable 状態での無効化要求を無視するための条件。

###### #139: turnOffCruise: CC停止 AND 統合 (Functional)
キャンセル操作と非Disable状態の2条件を AND で統合し、yesno を出力する。
- Rationale: CC動作中にキャンセル操作が行われた場合のみ停止するという仕様を AND で実装する。

##### #22: buttonsShouldBeCalledWhenActivated: アクティブ時限定ボタン操作の検出 (Container)
mode_prev がアクティブ状態であり、かつ ccsw_request が非null・非キャンセル要求のとき yesno = true を出力する。
- Rationale: inc/dec/set等のボタン操作はアクティブモード中にのみ有効とすべきであり、他のモードでの誤操作による意図しない遷移を防ぐためにアクティブ時限定の有効化条件を独立して判定する必要がある。

###### #127: bSCWA: Cruise 参照定数 (Functional)
reqMode.Cruise 定数を供給し、ccsw_request との比較に使用する。
- Rationale: アクティブ時限定ボタン操作の判定基準値（Cruise要求）を定数ブロックで管理する。

###### #128: bSCWA: Set 参照定数 (Functional)
reqMode.Set 定数を供給し、ccsw_request との比較に使用する。
- Rationale: アクティブ時限定ボタン操作の判定基準値（Set要求）を定数ブロックで管理する。

###### #129: bSCWA: Disable モード参照定数 (Functional)
opMode.Disable 定数を供給し、mode_prev との比較に使用する。
- Rationale: アクティブ判定の基準値を定数ブロックで管理する。

###### #130: bSCWA: ccsw_request!=Cruise 非等値比較 (Functional)
ccsw_request と reqMode.Cruise を ~= で比較し、Cruise 以外の要求かを判定する。
- Rationale: キャンセル/Cruise以外の要求を検出してアクティブ時操作を識別する。

###### #131: bSCWA: ccsw_request==Set 等値比較 (Functional)
ccsw_request と reqMode.Set を == で比較し、Set要求かを判定する。
- Rationale: アクティブ時限定のSet操作を検出する。

###### #132: bSCWA: mode_prev!=Disable 非等値比較 (Functional)
mode_prev と opMode.Disable を ~= で比較し、アクティブ状態かを判定する。
- Rationale: アクティブ時のみ有効な操作を確認するためのモード判定。

###### #133: bSCWA: アクティブ時操作 AND 統合 (Functional)
mode_prev!=Disable と ccsw_request!=Cruise の2条件を AND で統合する。
- Rationale: アクティブ中かつキャンセル以外の操作であることを AND で表現する。

###### #134: bSCWA: Set操作アクティブ時 AND 統合 (Functional)
アクティブ時操作AND結果と ccsw_request==Set を AND で統合し、yesno を出力する。
- Rationale: アクティブ状態中のSet操作を完全に特定する最終条件として AND で統合する。

##### #126: disableCondition: 無効化条件 OR 統合 (Functional)
turnOffCruise と buttonsShouldBeCalledWhenActivated の2条件を OR で統合し、無効化へ遷移すべきかを出力する。
- Rationale: CC停止操作とアクティブ時限定ボタン操作のどちらの条件でも無効化を発動させるため OR で統合する。

#### #15: enableCondition: 有効化条件の統合判定 (Container)
reqDrv と mode_prev から、有効化（Enable）モードへ遷移すべきかを示す yesno フラグを出力する。
- Rationale: 有効化条件はSetスイッチ押下と有効化キャンセル条件の組み合わせで決まるため、各判定を子サブシステムに分離して論理統合をここで行う必要がある。

##### #23: pressSetSw: Setスイッチ押下の検出 (Container)
reqDrv がSetスイッチ押下に対応する要求値と一致する場合に yesno = true を出力する。
- Rationale: Setスイッチ押下の検出を独立したサブシステムに分離することで、スイッチ種別の変更や追加をこのブロックのみの修正で対応可能にする必要がある。

###### #157: pressSetSw: Cruise 参照定数 (Functional)
reqMode.Cruise 定数を供給し、reqDrv との比較に使用する。
- Rationale: Setスイッチ押下（Cruise要求）の判定基準値を定数ブロックで管理する。

###### #158: pressSetSw: reqDrv==Cruise 等値比較 (Functional)
reqDrv と reqMode.Cruise を == で比較し、Setスイッチ押下を検出する。yesno として出力。
- Rationale: CC有効化のトリガーとなるSetスイッチ押下を単一の等値比較で実装する。

##### #24: cancelActivation: 有効化キャンセル条件の判定 (Container)
reqDrv がキャンセル操作を示し、かつ mode_prev がEnable状態のとき、有効化をキャンセルすべきであることを示す yesno = true を出力する。
- Rationale: 有効化操作が開始された後にキャンセル操作が行われた場合にEnable状態を脱出させる必要がある。この判定を分離することで有効化キャンセルの条件を明確に定義し保守性を高める。

###### #141: cancelActivation: IncrementHold 参照定数 (Functional)
opMode.IncrementHold を供給し、mode_prev との比較に使用する。
- Rationale: キャンセル条件のモード基準値を定数ブロックで管理する。

###### #142: cancelActivation: Increment 参照定数 (Functional)
opMode.Increment を供給し、mode_prev との比較に使用する。
- Rationale: キャンセル条件のモード基準値を定数ブロックで管理する。

###### #143: cancelActivation: Activate 参照定数 (Functional)
opMode.Activate を供給し、mode_prev との比較に使用する。
- Rationale: キャンセル条件のモード基準値を定数ブロックで管理する。

###### #144: cancelActivation: DecrementHold 参照定数 (Functional)
opMode.DecrementHold を供給し、mode_prev との比較に使用する。
- Rationale: キャンセル条件のモード基準値を定数ブロックで管理する。

###### #145: cancelActivation: Decrement 参照定数 (Functional)
opMode.Decrement を供給し、mode_prev との比較に使用する。
- Rationale: キャンセル条件のモード基準値を定数ブロックで管理する。

###### #146: cancelActivation: Cancel 要求参照定数 (Functional)
reqMode.Cancel を供給し、reqDrv との比較に使用する。
- Rationale: キャンセル操作検出の参照値を定数ブロックで管理する。

###### #147: cancelActivation: Resume 参照定数 (Functional)
opMode.Resume を供給し、mode_prev との比較に使用する。
- Rationale: キャンセル条件のモード基準値を定数ブロックで管理する。

###### #148: cancelActivation: mode_prev==IncrementHold 等値比較 (Functional)
mode_prev と opMode.IncrementHold を == で比較する。
- Rationale: キャンセル対象モードを個別の等値比較で判定する。

###### #149: cancelActivation: mode_prev==Increment 等値比較 (Functional)
mode_prev と opMode.Increment を == で比較する。
- Rationale: キャンセル対象モードを個別の等値比較で判定する。

###### #150: cancelActivation: mode_prev==Activate 等値比較 (Functional)
mode_prev と opMode.Activate を == で比較する。
- Rationale: キャンセル対象モードを個別の等値比較で判定する。

###### #151: cancelActivation: mode_prev==DecrementHold 等値比較 (Functional)
mode_prev と opMode.DecrementHold を == で比較する。
- Rationale: キャンセル対象モードを個別の等値比較で判定する。

###### #152: cancelActivation: mode_prev==Decrement 等値比較 (Functional)
mode_prev と opMode.Decrement を == で比較する。
- Rationale: キャンセル対象モードを個別の等値比較で判定する。

###### #153: cancelActivation: reqDrv==Cancel 等値比較 (Functional)
reqDrv と reqMode.Cancel を == で比較し、キャンセル操作を検出する。
- Rationale: Cancel 操作の入力を独立した比較で検出する。

###### #154: cancelActivation: mode_prev==Resume 等値比較 (Functional)
mode_prev と opMode.Resume を == で比較する。
- Rationale: Resume 中のキャンセルも対象とするための等値比較。

###### #155: cancelActivation: キャンセル対象モード OR 統合 (Functional)
7種のアクティブ/Resume系モードの等値比較を OR で統合する。
- Rationale: いずれかのアクティブ系モードでキャンセルが可能という仕様を OR で実装する。

###### #156: cancelActivation: キャンセル条件 AND 統合 (Functional)
キャンセル対象モード OR 結果と reqDrv==Cancel を AND で統合し、yesno を出力する。
- Rationale: アクティブ系モード中にキャンセル操作があった場合のみ有効化をキャンセルする。

##### #140: enableCondition: 有効化条件 OR 統合 (Functional)
pressSetSw と cancelActivation の2条件を OR で統合し、Enable モードへの遷移条件を出力する。
- Rationale: Setスイッチ押下と有効化キャンセルどちらの経路でも Enable へ移行させるため OR で統合する。

#### #16: resumeCondition: 再開条件の統合判定 (Container)
reqDrv と mode_prev から、再開（Resume）モードへ遷移すべきかを示す yesno フラグを出力する。
- Rationale: 再開条件はEnable状態からの再開操作とキャンセル済み状態の検出の論理和で決まるため、各判定を子サブシステムで評価し最終判定をここで統合する必要がある。

##### #25: enableToResume: Enable状態からの再開条件判定 (Container)
reqDrv がResume要求であり、かつ mode_prev がEnable状態のとき、yesno = true を出力する。
- Rationale: Enable状態からResume操作によってResume状態へ遷移するパスを独立したサブシステムで判定することで、この遷移条件の仕様を局所化し変更の影響範囲を限定する必要がある。

###### #160: enableToResume: ResumeReq 参照定数 (Functional)
reqMode.ResumeReq 定数を供給し、reqDrv との比較に使用する。
- Rationale: Resume 遷移要求の判定基準値を定数ブロックで管理する。

###### #161: enableToResume: Enable モード参照定数 (Functional)
opMode.Enable 定数を供給し、mode_prev との比較に使用する。
- Rationale: Enable 状態からの Resume 遷移条件の判定基準値を定数ブロックで管理する。

###### #162: enableToResume: reqDrv==ResumeReq 等値比較 (Functional)
reqDrv と reqMode.ResumeReq を == で比較し、Resume 要求を検出する。
- Rationale: Resume への遷移トリガーとなる操作要求を独立した比較で検出する。

###### #163: enableToResume: mode_prev==Enable 等値比較 (Functional)
mode_prev と opMode.Enable を == で比較し、Enable 状態かを確認する。
- Rationale: Enable 状態からのみ Resume へ遷移可能という制約を独立した比較で表現する。

###### #164: enableToResume: Enable から Resume 遷移 AND 統合 (Functional)
reqDrv==ResumeReq と mode_prev==Enable の2条件を AND で統合し、yesno を出力する。
- Rationale: Enable 中に Resume 要求があった場合のみ Resume へ遷移するという仕様を AND で実装する。

##### #26: hasCanceled: キャンセル状態の検出 (Container)
前ステップのモード履歴に基づき、直前にキャンセル操作が行われた状態かどうかを示す yesno フラグを遅延と論理演算を用いて生成する。
- Rationale: Resume操作を有効にするためには「一度Disableになった」という過去状態を記憶する必要がある。この状態記憶を独立したサブシステムに分離することで、キャンセル履歴の検出ロジックを他の遷移条件から独立して管理できる。

###### #165: hasCanceled: Disable モード参照定数1 (Functional)
opMode.Disable を供給し、mode_prev との比較および Switch への入力として使用する。
- Rationale: キャンセル状態追跡のための基準値を定数ブロックで管理する。

###### #166: hasCanceled: Enable モード参照定数1 (Functional)
opMode.Enable を供給し、Switch への入力として使用する。
- Rationale: キャンセル後の状態遷移で Enable を選択するための定数を管理する。

###### #167: hasCanceled: Enable モード参照定数2 (Functional)
hasCanceled の Delay2 初期値用 Enable 定数として使用する。
- Rationale: Delay の初期値として Enable を提供し、起動直後の hasCanceled 出力を正しく初期化する。

###### #168: hasCanceled: Disable モード参照定数2 (Functional)
hasCanceled の Switch 系への入力として使用する。
- Rationale: キャンセル検出時に Disable を出力するための定数を管理する。

###### #169: hasCanceled: mode_prev!=Enable 非等値比較 (Functional)
mode_prev と opMode.Enable を ~= で比較し、Enable 以外の状態かを判定する。
- Rationale: キャンセル後の状態変化を検出するための条件判定。

###### #170: hasCanceled: mode_prev==Enable 等値比較 (Functional)
mode_prev と opMode.Enable を == で比較し、Enable 状態かを判定する。
- Rationale: Enable 状態中のキャンセル発生を確認するための等値比較。

###### #171: hasCanceled: Delay1出力との等値比較 (Functional)
Delay1 の出力（1サンプル前のモード）と mode_prev を == で比較し、モードが変化したかを検出する。
- Rationale: 1サンプル前と現在のモードを比較することでキャンセルによるモード変化を捉える。

###### #172: hasCanceled: mode_prev!=Disable 非等値比較 (Functional)
mode_prev と opMode.Disable を ~= で比較し、Disable 以外であることを確認する。
- Rationale: キャンセル検出の前提として、現在 Disable でないことを確認する。

###### #173: hasCanceled: モード履歴 Delay1 (Functional)
mode_prev を 1 サンプル遅延させ、前々サンプルのモードとして参照する。初期値は opMode.Disable。
- Rationale: モード変化の検出には少なくとも1サンプル前の状態が必要であるため Delay で保持する。

###### #174: hasCanceled: キャンセルフラグ Delay2 (Functional)
キャンセル状態フラグを 1 サンプル遅延させて次サンプルに引き継ぐ。初期値は false。
- Rationale: キャンセル状態は1サンプル継続して Resume 判定に使用されるため Delay で保持する。

###### #175: hasCanceled: true 定数 (Functional)
キャンセル検出時の出力値 true を供給する。
- Rationale: キャンセル成立時に yesno=true を出力するための定数を管理する。

###### #176: hasCanceled: false 定数 (Functional)
キャンセル非検出時の出力値 false を供給する。
- Rationale: キャンセル不成立時に yesno=false を出力するための定数を管理する。

###### #177: hasCanceled: キャンセル検出 AND1 (Functional)
モード変化検出と mode_prev!=Disable の2条件を AND で統合する。
- Rationale: Disable 以外の状態でモード変化が起きたことを AND で表現し、キャンセル発生を検出する。

###### #178: hasCanceled: キャンセル継続 AND2 (Functional)
mode_prev==Enable と Delay2の前サンプルフラグを AND で統合する。
- Rationale: Enable 状態中にキャンセルフラグが立っている場合にキャンセル継続と判定する。

###### #179: hasCanceled: キャンセル状態 Switch1 (Functional)
AND1 が true のとき true 定数を、false のとき Delay2 出力をパススルーする。
- Rationale: キャンセルが新たに検出された場合にフラグを true に切り替え、それ以外は前サンプルフラグを維持する。

###### #180: hasCanceled: キャンセル出力 Switch2 (Functional)
AND2 が true のとき true 定数を、false のとき false 定数を yesno として出力する。
- Rationale: Enable 中にキャンセルフラグが継続している場合のみ yesno=true を出力し、Resume 遷移の前提条件を生成する。

##### #159: resumeCondition: Resume 遷移条件 AND 統合 (Functional)
enableToResume と hasCanceled の2条件を AND で統合し、Resume モードへ遷移すべきかを出力する。
- Rationale: Resume は過去のキャンセル履歴と現在の Resume 要求が同時に成立した場合のみ許可されるため AND で統合する。

#### #27: IncrementDecrement: インクリメント/デクリメント操作時のモード選択 (Container)
reqDrv がインクリメントまたはデクリメント要求のいずれかと一致するとき、その要求に対応する動作モード値を mode として出力する。いずれにも一致しない場合は mode_prev をそのまま出力する。
- Rationale: inc/dec 操作によるモード遷移は他の有効化・無効化・再開条件とは独立したパスであるため、専用のサブシステムで要求値とモード値の対応関係を管理することで、遷移ルールの変更を局所化し保守性を高める必要がある。

##### #84: IncrementDecrement: Inc_Short 参照定数 (Functional)
reqMode.Inc_Short 定数を供給し、reqDrv との比較に使用する。
- Rationale: 押下種別判定のための参照値を定数ブロックで管理する。

##### #85: IncrementDecrement: Increment モード出力定数 (Functional)
opMode.Increment 定数を供給し、Switch チェーンへの出力候補とする。
- Rationale: インクリメント短押し時に選択されるモード値を定数ブロックで管理する。

##### #86: IncrementDecrement: Dec_Long 参照定数 (Functional)
reqMode.Dec_Long 定数を供給し、reqDrv との比較に使用する。
- Rationale: デクリメント長押し判定のための参照値を定数ブロックで管理する。

##### #87: IncrementDecrement: Dec_Short 参照定数 (Functional)
reqMode.Dec_Short 定数を供給し、reqDrv との比較に使用する。
- Rationale: デクリメント短押し判定のための参照値を定数ブロックで管理する。

##### #88: IncrementDecrement: Decrement モード出力定数 (Functional)
opMode.Decrement 定数を供給し、Switch チェーンへの出力候補とする。
- Rationale: デクリメント短押し時に選択されるモード値を定数ブロックで管理する。

##### #89: IncrementDecrement: Inc_Long 参照定数 (Functional)
reqMode.Inc_Long 定数を供給し、reqDrv との比較に使用する。
- Rationale: インクリメント長押し判定のための参照値を定数ブロックで管理する。

##### #90: IncrementDecrement: IncrementHold モード出力定数 (Functional)
opMode.IncrementHold 定数を供給し、Switch チェーンへの出力候補とする。
- Rationale: インクリメント長押し時に選択されるモード値を定数ブロックで管理する。

##### #91: IncrementDecrement: DecrementHold モード出力定数 (Functional)
opMode.DecrementHold 定数を供給し、Switch チェーンへの出力候補とする。
- Rationale: デクリメント長押し時に選択されるモード値を定数ブロックで管理する。

##### #92: IncrementDecrement: Inc_Short 等値比較 (Functional)
reqDrv と reqMode.Inc_Short を == で比較し、インクリメント短押しを検出する。
- Rationale: インクリメント短押し選択条件を独立した RelationalOperator で表現する。

##### #93: IncrementDecrement: Dec_Short 等値比較 (Functional)
reqDrv と reqMode.Dec_Short を == で比較し、デクリメント短押しを検出する。
- Rationale: デクリメント短押し選択条件を独立した RelationalOperator で表現する。

##### #94: IncrementDecrement: Inc_Long 等値比較 (Functional)
reqDrv と reqMode.Inc_Long を == で比較し、インクリメント長押しを検出する。
- Rationale: インクリメント長押し選択条件を独立した RelationalOperator で表現する。

##### #95: IncrementDecrement: Dec_Long 等値比較 (Functional)
reqDrv と reqMode.Dec_Long を == で比較し、デクリメント長押しを検出する。
- Rationale: デクリメント長押し選択条件を独立した RelationalOperator で表現する。

##### #96: IncrementDecrement: Inc_Short 選択 Switch1 (Functional)
Inc_Short 一致時に opMode.Increment を出力し、不一致時は下段をパススルーする。
- Rationale: インクリメント短押しに対応するモードを選択する Switch。

##### #97: IncrementDecrement: Dec_Short 選択 Switch5 (Functional)
Dec_Short 一致時に opMode.Decrement を出力し、不一致時は下段をパススルーする。
- Rationale: デクリメント短押しに対応するモードを選択する Switch。

##### #98: IncrementDecrement: Inc_Long 選択 Switch6 (Functional)
Inc_Long 一致時に opMode.IncrementHold を出力し、不一致時は下段をパススルーする。
- Rationale: インクリメント長押しに対応するモードを選択する Switch。

##### #99: IncrementDecrement: Dec_Long 選択 Switch7 (Functional)
Dec_Long 一致時に opMode.DecrementHold を出力し、不一致時は mode_prev をパススルーする。
- Rationale: デクリメント長押しに対応するモードを選択する Switch。条件不成立時は前サンプルモードを維持する。

#### #73: opMode: Disable モード定数 (Functional)
Switch チェーンへの入力として opMode.Disable 列挙定数を供給する。
- Rationale: 各 Switch の選択肢として使用するモード列挙値を定数ブロックで明示し、値の一元管理を行う。

#### #74: opMode: Enable モード定数 (Functional)
Switch チェーンへの入力として opMode.Enable 列挙定数を供給する。
- Rationale: 各 Switch の選択肢として使用するモード列挙値を定数ブロックで明示し、値の一元管理を行う。

#### #75: opMode: Activate モード定数 (Functional)
Switch チェーンへの入力として opMode.Activate 列挙定数を供給する。
- Rationale: 各 Switch の選択肢として使用するモード列挙値を定数ブロックで明示し、値の一元管理を行う。

#### #76: opMode: Resume モード定数 (Functional)
Switch チェーンへの入力として opMode.Resume 列挙定数を供給する。
- Rationale: 各 Switch の選択肢として使用するモード列挙値を定数ブロックで明示し、値の一元管理を行う。

#### #77: opMode: NoRequest 参照定数 (Functional)
keepActivated 条件内で reqDrv との比較に使用する reqMode.NoRequest 定数を供給する。
- Rationale: 操作要求が存在しない状態の判定基準を定数ブロックで明示する。

#### #78: opMode: outRange 等値比較 (Functional)
outRange フラグと false（範囲内）を == で比較し、車速が制御範囲内かどうかを判定する。
- Rationale: activateCondition への入力として速度範囲内を確認するため、outRange フラグの等値判定を行う。

#### #79: opMode: resumeCondition 選択 Switch (Functional)
resumeCondition が true のとき opMode.Resume を出力し、false のとき下段の Switch 出力をパススルーする。
- Rationale: Resume モードへの遷移条件成立時に Resume を選択するための Switch。条件別に Switch を直列化することでモード選択の優先度を明示する。

#### #80: opMode: enableCondition 選択 Switch2 (Functional)
enableCondition が true のとき opMode.Enable を出力し、false のとき下段の Switch 出力をパススルーする。
- Rationale: Enable モードへの遷移条件成立時に Enable を選択するための Switch。

#### #81: opMode: activateCondition 選択 Switch3 (Functional)
activateCondition が true のとき IncrementDecrement または Activate の出力を選択し、false のとき下段の Switch 出力をパススルーする。
- Rationale: アクティブ化条件成立時に Activate 系モードを選択するための Switch。

#### #82: opMode: disableCondition 選択 Switch4 (Functional)
disableCondition が true のとき opMode.Disable を出力し、false のとき mode_prev（前サンプルモード）をパススルーする。
- Rationale: 無効化条件成立時に Disable に切り替え、条件不成立時は前サンプルモードを維持することでモードの持続性を保証する。

#### #83: opMode: outRange 無効化 Switch8 (Functional)
outRange が true のとき opMode.Enable を出力し、false のとき上段の Switch チェーン出力をパススルーする。
- Rationale: 車速が範囲外になった場合に Activate への遷移を禁止し Enable に留まらせることで、範囲外速度でのアクティブ化を防止する。

#### #236: frontDistance single入力の受け渡し (Functional)
CruiseControlMode は、前方車両との距離をミリメートル単位の single 型 frontDistance 入力として受け取り、モード遷移判定に使用できるよう opMode へ受け渡さなければならない。
- Rationale: 前方距離センサーは新規の外部入力である。トップモデル、CruiseControlMode、opMode を通して信号を受け渡すことで、既存のサブシステム責務を保ったままモード選択ロジックで距離情報を利用できるようにするため。
- Keywords: draft, frontDistance, interface, auto-enable

#### #237: frontDistance 5m閾値判定 (Functional)
frontDistance が FrontDistanceThreshold_mm (5000 mm) 以下のとき、CruiseControlMode は前方車両が5 m以内に存在する状態として判定しなければならない。
- Rationale: 5 m は要求された前方車両距離の境界値である。閾値を Data Dictionary の Simulink.Parameter である FrontDistanceThreshold_mm として管理することで、モデル内の直値を避け、キャリブレーション値の管理箇所を明確にするため。
- Keywords: draft, frontDistance, threshold, auto-enable

#### #238: Activate中の前方距離による自動Enable遷移 (Functional)
動作モードが opMode.Activate の間に frontDistance が FrontDistanceThreshold_mm (5000 mm) 以下になった場合、CruiseControlMode は動作モードを opMode.Enable へ遷移させなければならない。
- Rationale: 前方車両が5 m以内に検出された場合に Activate から Enable へ戻すことで、アクティブなクルーズ制御を継続しない一方、運転者の次操作に備えた Enable 状態を維持するため。追加条件は既存の enableCondition と OR 結合しており、従来の運転者要求による Enable 遷移を保持する。
- Keywords: draft, frontDistance, mode-transition, auto-enable

#### #239: 非Activate状態または5m超過時の自動Enable抑止 (Functional)
動作モードが opMode.Activate ではない場合、または frontDistance が FrontDistanceThreshold_mm (5000 mm) を超える場合、frontDistance は単独で opMode.Enable への遷移を指令してはならない。
- Rationale: 距離閾値判定を opMode.Activate 状態でゲートすることで、近距離のセンサー値によって Disable、Enable、Resume、Increment、Decrement などの他モードが意図せず変化することを防ぐため。追加機能の影響範囲をアクティブなクルーズ制御状態に限定する。
- Keywords: draft, frontDistance, mode-transition, auto-enable

### #56: CruiseControlMode 初期モード定数 (Functional)
opMode サブシステムが未実行のとき（初回サンプル時など）に Switch に渡す初期モード値（opMode.Disable）を EnumeratedConstant で供給する。
- Rationale: UnitDelay の初期値と揃えることで、起動直後に Disable 状態を正しく維持するために必要な定数を提供する。

### #57: モード有効判定 Switch (Functional)
disable_flag が false（無効化条件なし）のとき opMode 出力を選択し、true のとき初期値（Disable）を出力する。
- Rationale: 強制無効化条件が発生した場合に即座に Disable モードへ切り替えるため、disableCaseDetection の出力を最終モード決定に組み込む。

### #58: 前サンプルモード保持 UnitDelay (Functional)
現在サンプルの mode 出力を 1 サンプル遅延させ、次サンプルにおける mode_prev として opMode サブシステムへ供給する。初期値は opMode.Disable。
- Rationale: opMode 内の各条件判定（activateCondition など）は前サンプルのモード（mode_prev）を参照するため、1サンプル前の値を保持する Delay が必要である。

## #3: TargetSpeedThrottle: 目標速度とスロットル指令値の算出 (Container)
制御モード（mode）、車速（vehSp）、ドライバースロットル（throtDrv）を入力として、目標速度（targetSp）とクルーズコントロール用スロットル指令値（throtCC）を算出する。
- Rationale: モードに応じて制御則（無効・有効・アクティブ・再開）を切り替え、適切なスロットル出力を生成することで、車速を目標値に追従させる制御ループを実現する必要がある。

### #181: toBoolean: 動作モードのブール変換 (Container)
入力 mode（opMode 列挙値）を Disable / Enable / Resume / Activate の各ブール信号（isDisabled / isEnabled / isResumed / isActivated）に変換する。
- Rationale: 後続サブシステム（disabled / enabled / activated）のイネーブル制御および targetSpeed の格納条件判断に使用するため、モード列挙値をブール値に分解する必要がある。

#### #191: opMode.Disable 定数の定義 (Functional)
opMode.Disable を列挙定数として定義し、relop1 の比較基準値として供給する。
- Rationale: 列挙型定数を明示的に定義することで、比較演算に型安全性と可読性を与える。

#### #192: opMode.Resume 定数の定義 (Functional)
opMode.Resume を列挙定数として定義し、relop3 の比較基準値として供給する。
- Rationale: 列挙型定数を明示的に定義することで、比較演算に型安全性と可読性を与える。

#### #193: opMode.Enable 定数の定義 (Functional)
opMode.Enable を列挙定数として定義し、relop2 の比較基準値として供給する。
- Rationale: 列挙型定数を明示的に定義することで、比較演算に型安全性と可読性を与える。

#### #194: Disable モードの判定 (Functional)
mode == opMode.Disable のとき true を出力し、isDisabled 信号として後続の disabled サブシステムイネーブルに供給する。
- Rationale: クルーズ無効状態を他のモードと区別するため、個別のブール信号として抽出する。

#### #195: Enable モードの判定 (Functional)
mode == opMode.Enable のとき true を出力し、isEnabled 信号として enabled サブシステムイネーブルと targetSpeed の格納条件に供給する。
- Rationale: クルーズ有効待機状態を他のモードと区別するため、個別のブール信号として抽出する。

#### #196: Resume モードの判定 (Functional)
mode == opMode.Resume のとき true を出力し、isResumed 信号として targetSpeed の再開選択に供給する。
- Rationale: 一時解除後の再開状態を他のモードと区別するため、個別のブール信号として抽出する。

#### #197: Activate モードの判定（NOR） (Functional)
isDisabled / isEnabled / isResumed の NOR 演算により、これらすべてが false のとき（すなわち mode == Activate のとき）true を出力して isActivated 信号とする。
- Rationale: クルーズアクティブ状態は他の 3 モードのいずれでもない状態として定義されるため、NOR によるデコードが適切である。

### #182: disabled: クルーズ無効時の出力 (Container)
クルーズ無効（Disable）モード時に目標速度として最小値（tsp_min = 40 km/h）を出力し、スロットル指令値はドライバー入力（throtDrv）をパススルーする。
- Rationale: 無効状態では目標速度を保持する意味がないため、最小値を出力してシステムの初期状態を明示する。

#### #198: 無効時の目標速度最小値定数（tsp_min = 40 km/h） (Functional)
クルーズ無効（Disable）モード時の目標速度として tsp_min（40 km/h）を定数出力する。
- Rationale: 無効状態の初期目標速度を最小許容値に設定することで、再有効化時の安全なデフォルト動作を保証する。

### #183: enabled: クルーズ有効待機時の出力 (Container)
有効（Enable）モード時に車速（vehSp）を目標速度として、ドライバースロットル（throtDrv）をスロットル指令値としてパススルーする。
- Rationale: クルーズ有効待機中はアクティベートを待つため、現在の車速を目標速度とし、クルーズ制御を介入させない。

### #184: targetSpeed: 目標速度の状態管理 (Container)
再開（Resume）時は格納済み目標速度を、それ以外は前サンプルの Merge 出力を目標速度として供給する。アクティブ→有効への遷移時に storeSpeed が目標速度を格納する。
- Rationale: クルーズを一時解除した後に再開する際、解除前の目標速度を復元するために状態保持機構が必要である。

#### #185: storeSpeed: 目標速度のサンプルホールド (Container)
LogicOp1 がアサートされたサンプルに限り、前サンプルの目標速度（targetSp_prev）をイネーブルサブシステムのホールド動作で保持して出力する。
- Rationale: Resume 時に参照する格納済み目標速度を保持するため、アクティブ→有効遷移のタイミングでサンプルホールドが必要である。

#### #199: 前サンプルの Activate 信号保持（UnitDelay1） (Functional)
isActivated を 1 サンプル遅延させ、LogicOp1 の入力として供給する。
- Rationale: アクティブ→有効への遷移（isActivated の立ち下がり）を検出するため、前サンプルの isActivated が必要である。

#### #200: スピード格納条件の論理積（LogicOp1） (Functional)
isEnabled（現サンプルで有効モード）と UnitDelay1 出力（前サンプルの isActivated）の AND を算出し、storeSpeed サブシステムのイネーブル信号として使用する。
- Rationale: アクティブから有効へ遷移した直後のサンプルでのみ目標速度を格納することで、最後のアクティブ目標速度を保持できる。

#### #201: 再開時の目標速度選択（Switch5） (Functional)
isResumed が true のとき storeSpeed の格納済み目標速度を、false のとき前サンプルの Merge 出力（targetSp_in）を選択して出力する。
- Rationale: Resume 時にクルーズ解除前の目標速度を復元するため、格納値と現在値を切り替える選択が必要である。

### #186: activated: アクティブ時の目標速度・スロットル算出 (Container)
アクティブ（Activate）モード時に、操作モード（mode）に応じた目標速度を算出するとともに、PI 制御またはドライバースロットルを用いてスロットル指令値を出力する。
- Rationale: クルーズコントロールがアクティブな間、ドライバーのスイッチ操作に応じた速度変更と、車速を目標速度に追従させる制御則が必要である。

#### #187: getNewTargetSpeed: 操作モードに応じた目標速度の更新 (Container)
操作モード（Activate / Increment / IncrementHold / Decrement / DecrementHold）に応じて目標速度を保持・増減させ、許容範囲 [tsp_min = 40, tsp_max = 100] km/h にクランプして出力する。
- Rationale: ドライバーのスイッチ操作をリアルタイムで目標速度に反映し、安全な速度範囲内に収めるために必要である。

##### #202: opMode.Activate 定数の定義（getNewTargetSpeed） (Functional)
opMode.Activate を列挙定数として定義し、RelationalOperator2 の比較基準値として供給する。
- Rationale: 型安全な列挙型比較を行うため、モード定数を明示的に定義する。

##### #203: opMode.IncrementHold 定数の定義 (Functional)
opMode.IncrementHold を列挙定数として定義し、RelationalOperator3 の比較基準値として供給する。
- Rationale: 型安全な列挙型比較を行うため、モード定数を明示的に定義する。

##### #204: opMode.Increment 定数の定義 (Functional)
opMode.Increment を列挙定数として定義し、RelationalOperator1 の比較基準値として供給する。
- Rationale: 型安全な列挙型比較を行うため、モード定数を明示的に定義する。

##### #205: opMode.Decrement 定数の定義 (Functional)
opMode.Decrement を列挙定数として定義し、RelationalOperator4 の比較基準値として供給する。
- Rationale: 型安全な列挙型比較を行うため、モード定数を明示的に定義する。

##### #206: 短押しインクリメント量定数（target_inc_short = 1 km/h） (Functional)
Increment 操作時に目標速度に加算する増分量 target_inc_short（1 km/h）を定数として定義し、Add1 に供給する。
- Rationale: 短押し操作に対する目標速度の増分量を定数として明示し、パラメータ変更を容易にする。

##### #207: 長押しインクリメント量定数（target_inc_hold = 0.05 km/h） (Functional)
IncrementHold 操作時に目標速度に加算する増分量 target_inc_hold（0.05 km/h）を定数として定義し、Add2 に供給する。
- Rationale: 長押し操作に対する目標速度の微小増分量を定数として明示し、パラメータ変更を容易にする。

##### #208: 短押しデクリメント量定数（target_dec_short = 1 km/h） (Functional)
Decrement 操作時に目標速度から減算する減分量 target_dec_short（1 km/h）を定数として定義し、Add3 に供給する。
- Rationale: 短押し操作に対する目標速度の減分量を定数として明示し、パラメータ変更を容易にする。

##### #209: 長押しデクリメント量定数（target_dec_hold = 0.05 km/h） (Functional)
DecrementHold 操作時に目標速度から減算する減分量 target_dec_hold（0.05 km/h）を定数として定義し、Add4 に供給する。
- Rationale: 長押し操作に対する目標速度の微小減分量を定数として明示し、パラメータ変更を容易にする。

##### #210: Increment 短押し後の目標速度計算（Add1） (Functional)
targetSpIn に target_inc_short（1 km/h）を加算し、Increment 操作時の目標速度候補値を算出する。
- Rationale: Increment 操作の結果を Switch1 で選択できるよう事前に計算する。

##### #211: IncrementHold 長押し後の目標速度計算（Add2） (Functional)
targetSpIn に target_inc_hold（0.05 km/h）を加算し、IncrementHold 操作時の目標速度候補値を算出する。
- Rationale: IncrementHold 操作の結果を Switch2 で選択できるよう事前に計算する。

##### #212: Decrement 短押し後の目標速度計算（Add3） (Functional)
targetSpIn から target_dec_short（1 km/h）を減算し、Decrement 操作時の目標速度候補値を算出する。
- Rationale: Decrement 操作の結果を Switch3 で選択できるよう事前に計算する。

##### #213: DecrementHold 長押し後の目標速度計算（Add4） (Functional)
targetSpIn から target_dec_hold（0.05 km/h）を減算し、DecrementHold 操作時の目標速度候補値を算出する。
- Rationale: DecrementHold 操作の結果を Switch3 のデフォルト入力として使用できるよう事前に計算する。

##### #214: Increment モードの判定（RelationalOperator1） (Functional)
mode == opMode.Increment のとき true を出力し、Switch1 の選択制御信号として使用する。
- Rationale: 4 段階の速度変化モードを個別の Switch に振り分けるため、各モードを個別に判定する。

##### #215: Activate モードの判定（RelationalOperator2） (Functional)
mode == opMode.Activate のとき true を出力し、Switch の選択制御信号として使用する。Activate 時は目標速度を変更せず保持する。
- Rationale: Activate モードでは速度変化を行わない（保持）ことを実装するため、個別に判定する。

##### #216: IncrementHold モードの判定（RelationalOperator3） (Functional)
mode == opMode.IncrementHold のとき true を出力し、Switch2 の選択制御信号として使用する。
- Rationale: 4 段階の速度変化モードを個別の Switch に振り分けるため、各モードを個別に判定する。

##### #217: Decrement モードの判定（RelationalOperator4） (Functional)
mode == opMode.Decrement のとき true を出力し、Switch3 の選択制御信号として使用する。
- Rationale: 4 段階の速度変化モードを個別の Switch に振り分けるため、各モードを個別に判定する。

##### #218: Activate 時の目標速度保持選択（Switch） (Functional)
mode == Activate のとき targetSpIn をそのまま通過させる（目標速度保持）。Activate でないとき Switch1 の出力を選択する。
- Rationale: アクティベート直後に目標速度が変化しないよう、Activate モードでは現在値を保持するための優先選択が必要である。

##### #219: Increment 時の短押し速度選択（Switch1） (Functional)
mode == Increment のとき Add1 の出力（targetSpIn + 1 km/h）を選択する。Increment でないとき Switch2 の出力を選択する。
- Rationale: 優先度チェーンにより Increment モードを Activate より低優先で処理するための選択ブロックが必要である。

##### #220: IncrementHold 時の長押し速度選択（Switch2） (Functional)
mode == IncrementHold のとき Add2 の出力（targetSpIn + 0.05 km/h）を選択する。IncrementHold でないとき Switch3 の出力を選択する。
- Rationale: 優先度チェーンにより IncrementHold モードを Increment より低優先で処理するための選択ブロックが必要である。

##### #221: Decrement / DecrementHold 時の速度選択（Switch3） (Functional)
mode == Decrement のとき Add3 の出力（targetSpIn - 1 km/h）を選択する。Decrement でないとき（DecrementHold）Add4 の出力（targetSpIn - 0.05 km/h）を選択する。
- Rationale: 優先度チェーンの末端として Decrement と DecrementHold を 1 つの Switch で処理する。DecrementHold はデフォルト（else）入力として扱われる。

##### #222: 目標速度の速度範囲クランプ（Saturation） (Functional)
Switch チェーンの出力を [tsp_min = 40 km/h, tsp_max = 100 km/h] にクランプし、目標速度が許容範囲を逸脱しないようにする。
- Rationale: 操作によって目標速度が安全範囲を超えないよう、出力段でリミッタを設けることが必要である。

#### #188: getThrottleValue: スロットル指令値の選択と制限 (Container)
PI 制御出力とドライバースロットルを UsePI の判定結果で切り替え、許容範囲 [throt_min = 0, throt_max = 100] % にクランプしてスロットル指令値を出力する。
- Rationale: PI 制御が車速を目標速度へ追従させる際に必要なスロットルを計算し、ドライバー操作との円滑な切り替えを実現するために必要である。

##### #189: PI controller: 比例積分制御によるスロットル計算 (Container)
目標速度と車速の偏差（targetSpIn - vehSp）を比例積分制御則で処理し、スロットル指令値（throt）を算出する。比例ゲイン Kp = 20、サンプル時間 Ts = 0.01 s。
- Rationale: 車速を目標速度に定常偏差なく追従させるため、比例項と積分項を組み合わせた閉ループ制御が必要である。

###### #223: 速度偏差の計算（Add） (Functional)
目標速度（targetSpIn）から車速（vehSp）を減算して速度偏差（e = targetSpIn - vehSp）を算出し、比例項・積分項の共通入力として供給する。
- Rationale: PI 制御則の起点となる偏差信号を生成するために必要である。

###### #224: 積分項の離散計算（DTI） (Functional)
速度偏差を離散積分（前進オイラー法）して積分項を算出する。更新式: y[k] = y[k-1] + e[k-1] * Ts（Ts = 0.01 s）。
- Rationale: 定常偏差を除去するため、積分項が必要である。PI controller がイネーブルのときのみ積分が更新される。

###### #225: 比例項の計算（Kp ゲイン） (Functional)
速度偏差に比例ゲイン Kp（= 20）を乗算して比例項（P 項）を算出する。
- Rationale: 速度偏差に即時応答するための比例制御を実現するために必要である。

###### #226: PI 制御出力の合算（Sum） (Functional)
比例項（Kp × e）と積分項（DTI 出力）を加算して PI 制御によるスロットル指令値（throt）を算出する。
- Rationale: 比例項と積分項を組み合わせることで定常偏差のない制御出力を生成するために必要である。

##### #190: UsePI: PI 制御使用条件の判定 (Container)
PI スロットル出力がドライバースロットル以上（throtPI >= throtDrv）、かつ目標速度が車速を超えている（targetSpIn > vehSp）とき、PI 制御を使用すると判定する。
- Rationale: 車速が目標速度を超えている場合や PI 出力がドライバー操作より小さい場合はドライバー操作を優先することで、制御の安全性と乗り心地を確保する。

###### #227: 目標速度超過判定（relop: targetSpIn > vehSp） (Functional)
目標速度（targetSpIn）が車速（vehSp）を上回るとき true を出力する。車速がまだ目標速度に達していない状態を判定する。
- Rationale: 車速が目標速度を超過している場合は PI スロットルが不要であるため、PI 使用条件の一部として判定する。

###### #228: PI スロットル優位性判定（RelationalOperator: throtPI >= throtDrv） (Functional)
PI 制御スロットル出力（throtPI）がドライバースロットル（throtDrv）以上のとき true を出力する。
- Rationale: ドライバーが PI 出力より大きいスロットルを踏んでいる場合は PI を無効化することで、ドライバー意図を優先する。

###### #229: PI 使用条件の論理積（LogicalOperator） (Functional)
throtPI >= throtDrv かつ targetSpIn > vehSp の両条件が成立するとき true を出力し、PI 制御を使用すると判定する（yesno 信号）。いずれかが false のときはドライバースロットルを優先する。
- Rationale: 2 つの独立した安全条件を AND 合成することで PI 使用の必要十分条件を判定するために必要である。

##### #230: 前サンプルの PI 使用フラグ保持（Delay1） (Functional)
UsePI の判定結果（yesno）を 1 サンプル遅延させ、PI controller サブシステムのイネーブル信号として使用する。
- Rationale: PI controller がイネーブルになる条件を 1 サンプル遅延させることで、現サンプルで PI 使用と判定されたとき次サンプルから積分を開始する設計とする。

##### #231: PI / ドライバースロットル選択（Switch） (Functional)
UsePI の判定結果（yesno）が true のとき PI controller 出力（throt）を、false のときドライバースロットル（throtDrv）を選択する。
- Rationale: PI 制御とドライバー操作を UsePI 条件に基づいて切り替えることで、安全なスロットル出力を選択する。

##### #232: スロットル指令値の範囲クランプ（Saturation2） (Functional)
Switch の出力を [throt_min = 0 %, throt_max = 100 %] にクランプし、物理的な許容範囲を保証する。
- Rationale: PI 制御の積分ワインドアップ等によりスロットル指令値が許容範囲を超えることを防止するために必要である。

### #233: 3 モードからの目標速度マージ（Merge） (Functional)
disabled / enabled / activated の各イネーブルサブシステムから出力される目標速度（targetSp）を Merge ブロックで統合し、有効状態のサブシステムの出力を最終 targetSp として選択する。
- Rationale: イネーブルサブシステムが排他的に動作するため、Merge ブロックによる統合で各モード出力をシングルワイヤに集約する必要がある。

### #234: 3 モードからのスロットル指令値マージ（Merge1） (Functional)
disabled / enabled / activated の各イネーブルサブシステムから出力されるスロットル指令値（throtCC）を Merge ブロックで統合し、有効状態のサブシステムの出力を最終 throtCC として選択する。
- Rationale: イネーブルサブシステムが排他的に動作するため、Merge ブロックによる統合でスロットル出力をシングルワイヤに集約する必要がある。

### #235: 前サンプル目標速度の保持（UnitDelay） (Functional)
Merge で統合された目標速度を 1 サンプル遅延させ、targetSpeed サブシステムの targetSp_in として供給する。
- Rationale: targetSpeed サブシステムが目標速度の前サンプル値を基準として Switch5 の選択を行うため、1 サンプル遅延による前値保持が必要である。
